module mobile_network {
  namespace "http://mobile-network.com";
  prefix "mobile-network";

  container subscribers {
    config true;

    list subscriber {
      key "number";

      leaf userName {
        config false;
        type string;
      }

      leaf number {
        type string;
      }

      leaf outgoingNumber {
        type string;
      }

      leaf incomingNumber {
        type string;
      }

      leaf status {
        type enumeration {
          enum "idle";
          enum "busy";
          enum "active";
        }
        default "idle";
      }
    }
  }
}
